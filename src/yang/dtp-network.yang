module dtp-network {

  namespace "http://www.cisco.com/dtp-network";
  prefix dtpn;

  import tailf-common { prefix tailf; }
  import tailf-ncs { prefix ncs; }
  import tailf-ncs-ned { prefix ned; }
  import ietf-inet-types { prefix inet; }

  description
    "Base model for network topology based services that use function objects.  The intent is to re-use the code that
    is a part of this package without changing it for any given network topology-based service.  Additional 
    packages should augment this model only where outlined so that the included code can read the model and 
    apply the function objects (NSO templates) at the right place";

  revision 2017-11-08 {
    description
      "Initial revision.";
  }

  grouping function-template {
    leaf template {
      type string;
      tailf:non-strict-leafref {
        path "/ncs:packages/ncs:package/ncs:templates";
      }
    }
  }
  grouping function-object {
    leaf name {
      type string;
    }
    uses function-template;
  }

  grouping authgroup {
    leaf authgroup {
      tailf:info "Authentication credentials for the device";
      type leafref {
        path "/ncs:devices/ncs:authgroups/ncs:group/ncs:name";
      }
      description
        "The authentication credentials used when connecting
         to this managed device.

         This leaf must be set for NETCONF and CLI devices, and
         may be used by generic NEDs, if applicable.";
    }
  }
  grouping ned-type {
    choice ne-type {
      case netconf {
        container netconf {
          presence "Use NETCONF to talk to the device";
/*
          must "../authgroup" {
            error-message
              "A NETCONF device must have a authgroup.";
            tailf:dependency "../authgroup";
          }
*/
          leaf ned-id {
            tailf:info "The NED Identity";
            type identityref {
              base ned:netconf-ned-id;
            }
            default ned:netconf;
            mandatory false;
          }

        }
      }
      case generic {
        container generic {
          tailf:info "Use a generic NED to talk to the device";
          presence "use a generic ned to communicate with the device";
/*
          must "../authgroup" {
            error-message
              "A Generic device must have a authgroup.";
            tailf:dependency "../authgroup";
          }
*/
          leaf ned-id {
            tailf:info "The NED Identity";
            type identityref {
              base ned:generic-ned-id;
            }
            mandatory true;
          }
        }
      }
      case cli {
        container cli {
          tailf:info "Use CLI to communicate with the device";
          presence "use CLI to communicate with the device";
/*
          must "../authgroup" {
            error-message
              "A CLI device must have a authgroup.";
            tailf:dependency "../authgroup";
          }
*/
          leaf ned-id {
            tailf:info "The NED Identity";
            type identityref {
              base ned:cli-ned-id;
            }
            mandatory true;
          }
          leaf protocol {
            tailf:info "The CLI protocol";
            type enumeration {
              enum telnet;
              enum ssh;
            }
            default ssh;
          }
        }
      }
    }
  }
  container dtp {
    description "Development to Production system";
    tailf:info "Development to Production system";

    list node-type {
      key "type";
      leaf type {
        type string;
      }
      container nso-device {
        uses authgroup;
        uses ned-type;
        container authorization {
          leaf username {
            mandatory true;
            type string;
          }
          leaf password {
            mandatory true;
            type string;
          }
          leaf secondary-password {
            type string;
          }
        }
        uses function-template {
          refine template {
            mandatory true;
            description "Template for registration of device to /devices/device";
            tailf:info "Template for registration of device to /devices/device";
          }
        }
      }
      container virl-device {
        leaf type {
          type enumeration {
            enum "SIMPLE";
          }
          default "SIMPLE";
        }
        leaf subtype {
          type enumeration {
            enum "IOS XRv";
          }
        }
        uses function-template {
          refine template {
            description "Virl device configuration template for the virl topology node";
            tailf:info "Virl device configuration template for the virl topology node";
          }
        }
        container day0-config {
          description "Day 0 configuration, choose either straight config or a template";
          tailf:info "Day 0 configuration, choose either straight config or a template";

          choice day0-config {
            case raw-config {
              leaf raw-config {
                description "Raw device configuraton text";
                tailf:info "Raw device configuraton text";
                type string;
              }
            }
            case template {
              uses function-template {
                refine template {
                  description "Virl device configuration template - sets the 'config' extension on the virl topology node";
                  tailf:info "Virl device configuration template - sets the 'config' extension on the virl topology node";
                }
              }
            }
          }
        }
      }
/*
      container physical-device {
        presence "Indicates that the device is a physical device";
        container day0-config {
          description "Day 0 configuration, choose either straight config or a template";
          tailf:info "Day 0 configuration, choose either straight config or a template";

          choice day0-config {
            case raw-config {
              leaf raw-config {
                description "Raw device configuraton text";
                tailf:info "Raw device configuraton text";
                type string;
              }
            }
            case template {
              uses function-template {
                refine template {
                  description "Virl device configuration template - sets the 'config' extension on the virl topology node";
                  tailf:info "Virl device configuration template - sets the 'config' extension on the virl topology node";
                }
              }
            }
          }
        }
      }
*/
    }

    list network {
      description "Network made up of topologies";

      key name;
      leaf name {
        description "Name of this network";
        tailf:info "Unique network service id";
        type string;
      }

      list node {
        description 
          "List of all the nodes(devices) that will be used in any of 
          this network's topologies";
        key name;
        leaf name {
          description 
            "Name of the node in the network.  Nodes listed here are 
            used across topologies in the network.";
          tailf:info "Name of the node in the network";
          type string;
        }
        leaf description {
          description "Description of this node and its purpose";
          tailf:info "Description of this node and its purpose";
          type string;
        }
        leaf node-type {
          mandatory "true";
          type leafref {
            path "../../../node-type/type";
          }
        }
        leaf deployment-target {
          mandatory "true";
          type leafref {
            path "../../deployment-target/name";
          }
        }
        leaf address {
          tailf:info "IP Address for the management interface";
          type inet:host;
          description
            "IP address or host name for the management interface on
             the device. If omitted the same address as configured for
             this device will be used.";
        }
        leaf mask {
          tailf:info "IP Address for the management interface";
          type inet:host;
          description
            "IP address or host name for the management interface on
             the device. If omitted the same address as configured for
             this device will be used.";
        }
        leaf port {
          tailf:info "Port for the management interface";
          type inet:port-number;
          description
            "Port for the management interface on the device.  If this leaf
             is not configured, NSO will use a default value based on
             the type of device.  For example, a NETCONF device uses
             port 830, a CLI device over SSH uses port 22, and a SNMP
             device uses port 161.";
        }
        container nso-device {
          leaf name {
            description "NSO device name";
            tailf:info "NSO device name";
//              mandatory "true";
            type string;
            tailf:non-strict-leafref {
              path "/ncs:devices/ncs:device/ncs:name";
            }
          }
//          uses authgroup;
        }
        uses state-grouping {
          refine state {
            config false;
            description "Current state of this node";
          }
        }
        tailf:action Update-State {
          tailf:actionpoint update-node-state-action;
          input {
            uses state-grouping {
              refine state {
                description "New state of this node";
              }
            }
          }
          output {
            leaf result {
              type string; 
            }
          }
        }
        tailf:action Check-Connectivity {
          tailf:actionpoint check-node-connectivity-action;
          input {}
          output {
            leaf result {
              type string; 
            }
          }
        }
      }

      list deployment-target {
        key name;
        leaf name {
          mandatory "true";
          type string;
        }
        container type {
          choice type {
            mandatory "true";
            case "Model-Only" {
              container Model-Only {
                presence "Model only target, nodes with this deployment target never get 
                          deployed or configured";
                description "Model only target, nodes with this deployment target never 
                            get deployed or configured";
                tailf:info "Model only target, nodes with this deployment target never 
                            get deployed or configured";
              }
            }
            case "Physical" {
              container Physical {
                presence "Node is a physical device";
                description "Node is a physical device";
                tailf:info "Node is a physical device";
              }
            }
            case "Virl" {
              container Virl {
                description "Virl deployment";
                tailf:info "Virl deployment";
                leaf virl-server {
                  description "NSO Virl server device";
                  tailf:info "NSO Virl server device";
                  mandatory "true";
                  type leafref {
                    path "/ncs:devices/ncs:device/ncs:name";
                  }
                  must "deref(current())/../ncs:module[ncs:name='cisco-virl']" {
                    tailf:dependency "/ncs:devices/ncs:device/ncs:module/ncs:name";
                  }
                }
                uses function-template {
                  refine template {
                    description "Virl topology base configuration template";
                    tailf:info "Virl topology base configuration template";
                  }
                }
              }
            }
          }
        }
//        must "count(../deployment-target[type='VIRL'])<2";
      }

      list topology {
        description "Topology (physical, logical, etc.) Service.  Modifying topologies can cause changes to the nodes it contains.";
        key name;
        leaf name {
          type string;
        }
        uses state-grouping;

        uses ncs:service-data;
//        ncs:servicepoint dtp-network-servicepoint;

        uses ncs:nano-plan-data;
        ncs:servicepoint dtp-topology-servicepoint;

//          choice deployment-target {
//            default model-only;
//            case model-only {
//              container model-only {
//                leaf callback-class {
//                  default "NONE";
//                  type enumeration {
//                    enum "NONE";
//                  }
//                }
//              }
//            }
//          }
        container virl-simulation-status {
          config false;
          leaf simulation-name {
            type string;
          }
          uses state-grouping;
        }
        tailf:action Update-State {
          tailf:actionpoint update-topology-virl-state-action;
          input {
            uses state-grouping {
              refine state {
                description "New state of this node";
              }
            }
          }
          output {
            leaf result {
              type string; 
            }
          }
        }
        list node {
          key name;
          leaf name {
            description "Name of the node in the topology";
            tailf:info "Name of the node in the topology";
            type leafref {
              path "../../../node/name";
            }
          }
/*
          container class {
            choice class {
            }
          }
*/
          container function-objects {}
        }
        list link {
          key name;
          leaf name {
            type string;
          }
          leaf type {
            type enumeration {
              enum "Single-Sided";
              enum "Two-Sided";
            }
          }
          list side {
            max-elements 2;
            key name;
            leaf name {
              type enumeration {
                enum "SIDE-A";
                enum "SIDE-B";
              }
            }
            leaf node {
              mandatory "true";
              type leafref {
                path "../../../node/name";
              }
            }
            container side-type {
              choice side-type {
              }
            }
            container function-objects {}
          }
          must "type = 'Two-Sided' or " +
              "(type = 'Single-Sided' and count(side) = 1)" {
                error-message "One-Sided Link can only have one side";
          }
          container function-objects {}
        }
        container function-objects {}

        tailf:action Track-Virl-Topology-Deployment {
          tailf:actionpoint VirlTopologyTracker;
          input {
          }
          output {
            leaf result {
              type string; 
            }
          }
        }
      }
    }
    container function-object-definitions {
      container network {
        list general {
          key name;
          uses function-object;
        }
      }
      container topology {}
      container node {}
      container link {
        container side {}
      }
    }
  }
  grouping state-grouping {
    leaf state {
      default "Modeled";
      type enumeration {
        enum "Error" {
          description "Cannot be configured";
          value "-1";
        }
        enum "Modeled" {
          description "Modeled";
          value "0";
        }
        enum "De-registered" {
          description "De-registered";
          value "1";
        }
        enum "Registered" {
          description "Registered";
          value "2";
        }
        enum "Undeploying" {
          description "Undeploying";
          value "3";
        }
        enum "Deploying" {
          description "Deploying";
          value "4";
        }
        enum "Deployed" {
          description "Deployed";
          value "5";
        }
        enum "Ready" {
          description "Ready for configuration";
          value "6";
        }
        enum "Configured" {
          description "Configured";
          value "7";
        }
      }
    }
  }

  identity dtp-plan { base ncs:plan-id; }
  identity deploy-virl-nodes { base ncs:plan-component-type; }
//  identity create-virl-register-tracker { base ncs:plan-state; }
  identity deploy-virl-topology { base ncs:plan-state; }
  identity register-nodes { base ncs:plan-component-type; }
  identity register-nodes-with-NSO { base ncs:plan-state; }
  identity node-connectivity { base ncs:plan-component-type; }
  identity check-connectivity { base ncs:plan-state; }
  identity apply-configuration { base ncs:plan-component-type; }
  identity topology-function-objects { base ncs:plan-state; }
  identity node-function-objects { base ncs:plan-state; }
  identity link-function-objects { base ncs:plan-state; }
  identity link_side-function-objects { base ncs:plan-state; }

  ncs:plan dtpn:dtp-plan {
    description "Topology Deployment Plan";

    ncs:component-type "ncs:self" {
      ncs:state "ncs:init";
      ncs:state "ncs:ready";
    }
    ncs:component-type "dtpn:register-nodes" {
      ncs:state "ncs:init";
      ncs:state "dtpn:register-nodes-with-NSO" {
        ncs:create {
          ncs:nano-callback;
        }
      }
      ncs:state "ncs:ready";
    }
    ncs:component-type "dtpn:node-connectivity" {
      ncs:state "ncs:init";
      ncs:state "dtpn:check-connectivity" {
        ncs:create {
          ncs:nano-callback;
        }
      }
      ncs:state "ncs:ready";
    }
    ncs:component-type "dtpn:deploy-virl-nodes" {
      ncs:state "ncs:init";
      ncs:state "dtpn:deploy-virl-topology" {
        ncs:create {
          ncs:nano-callback;
        }
      }
      ncs:state "ncs:ready" {
        ncs:create {
          ncs:monitor "$SERVICE/virl-simulation-status" {
            ncs:trigger-expr "current()[state = 'Deployed']";
          }
        }
      }
    }
    ncs:component-type "dtpn:apply-configuration" {
      ncs:state "ncs:init";
      ncs:state "dtpn:topology-function-objects" {
        ncs:create {
          ncs:nano-callback;
        }
      }
      ncs:state "dtpn:node-function-objects" {
        ncs:create {
          ncs:nano-callback;
        }
      }
      ncs:state "dtpn:link-function-objects" {
        ncs:create {
          ncs:nano-callback;
        }
      }
      ncs:state "dtpn:link_side-function-objects" {
        ncs:create {
          ncs:nano-callback;
        }
      }
      ncs:state "ncs:ready";
    }
  }

  ncs:behavior-tree dtp-topology-servicepoint {
    description "DTP Topology Behavior";
    ncs:plan-ref "dtpn:dtp-plan";
    ncs:selector {
      ncs:component "self" {
        ncs:component-type-ref "ncs:self";
      }
      ncs:component "Register Nodes" {
        ncs:component-type-ref "dtpn:register-nodes";
      }
      ncs:selector {
        ncs:create {
          ncs:monitor "$SERVICE/plan" {
            ncs:trigger-expr "current()/component[name='Register Nodes']/state[name='ncs:ready']
                                                                              [status='reached']";
          }
        }
        ncs:component "Deploy Virl Nodes" {
          ncs:component-type-ref "dtpn:deploy-virl-nodes";
        }
      }
      ncs:selector {
        ncs:create {
          ncs:monitor "$SERVICE/plan" {
            ncs:trigger-expr "current()/component[name='Register Nodes']/state[name='ncs:ready']
                                                                              [status='reached'] and 
                              current()/component[name='Deploy Virl Nodes']/state[name='ncs:ready']
                                                                                 [status='reached']";
          }
        }
        ncs:component "Check Node Connectivity" {
          ncs:component-type-ref "dtpn:node-connectivity";
        }
        ncs:component "Apply Topology Configurations" {
          ncs:create {
            ncs:monitor "/dtp/network/node" {
              ncs:trigger-expr "count(current()/../node[name=$SERVICE/node/name]
                                                       [state!='Ready']) = 0";
/*
              ncs:trigger-expr "current()/component[name='Register Nodes']/state[name='ncs:ready']
                                                                                [status='reached'] and 
                                current()/component[name='Deploy Virl Nodes']/state[name='ncs:ready']
                                                                                   [status='reached'] and 
                                count(current()/../../../node[name=current()/../node/name]
                                                       [state!='Ready']) = 0";
*/
            }
          }
          ncs:component-type-ref "dtpn:apply-configuration";
        }
      }
    }
  }
}
